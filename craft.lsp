;;;绘制草图
;*********************************************************************************************
;函数定义:InsertCraftPoint()
;功能：插入点,然后查找相邻点
;		点为图块,默认类型,并弹出对话框,输入点属性
;参数：
;返回：
;创建时间：2014/12/02   9:40
;修改时间：
;创建人：沈雄君
;*********************************************************************************************
(defun C:InsertCraftPoint ()
	(prompt "\n插入草图点.")
	(setq p1 (getpoint "拾取点坐标:"))
	;;根据点坐标查找点号
	;;如果是孤立点,则弹出对话框
	;;如果是已知单点,则提示连接到已知点吗?Y,则输入下一点;N,则提弹出对话框
	;;检查重复点号
	()
	
	;;
)

;;检查重复点号
